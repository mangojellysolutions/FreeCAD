from PIL import Image
import os
from PySide import QtGui
dir_path = os.path.dirname(os.path.realpath(__file__))

#Find the image
#Load the image

#imageWidth
#imageHeight

#colour to ignore
#what format is it in?
#explain with a black and white and a blue and white image
'''Try to use as smaller image as you can'''
img = Image.open(dir_path+"/images/smallmap.png", "r")
pix = img.load()

##get height and width
imgWidth = img.size[0]
imgHeight = img.size[1]
print("pixel size. width: "+str(imgWidth)+", height: "+str(imgHeight))

#Get a list of tuples, a tuple shows the pixel data for 1 pixel moving from left to righ as we descend
lst = list(img.getdata())
print("lst length: "+str(len(lst)))

#Shape params
'''we will plot a shape ever x pixels as long as that pixel is populated with the colour of the sea '''
pixelSpacing = 2
holeSize = 2
positionX = 0
positionY = 0
colourToIgnore = ()

##tuples are immutable this creates a new tuple for our ignore colour data
print("Defining colour to ignore from pixel at x:0, y:0 which has a channel structure of: " + str(lst[0]))
if ((type(lst[0]) is int) == False):
  for i in lst[0]:
    colourToIgnore = colourToIgnore + (0,)
else:
  colourToIgnore = 0
print("colour to ignore "+str(colourToIgnore))

##start stepping through the image
for y in range(0, imgHeight, pixelSpacing):
  positionY = pixelSpacing * y
  for x in range(0, imgWidth, pixelSpacing):
    positionX = pixelSpacing * x
    pixelIdx = x + imgWidth * y
	#compare the tuple. Note that you will have to change this depending on the amount of colour channels an / or colour to ignore       
    if (lst[pixelIdx] == colourToIgnore): 
      continue
    ##print ("x: "+str(x)+", y: "+str(y)+", pixel tuple["+str(pixelIdx)+"]: "+str(lst[pixelIdx]))
    App.ActiveDocument.Sketch.addGeometry(Part.Circle(App.Vector(positionX,positionY,0),App.Vector(0,0,1),holeSize/2),False)
    QtGui.QApplication.processEvents()
App.activeDocument().recompute()
print("Completed")
